# Stop_and_Wait

## Sender: Clarifying requirements of Sender part (Functional)

### SND-1: Packet should be create and send when a new data arrived (Functional)
The input data should be a uint8 form of a character and and a boolean which acts as an event which is used to verify if the input data is valid. If the event was active, the model should create an uint16 packet which contains data and its header. Then, the packet should send to other model.

### SND-2: Packet should have a tag and a header (Functional)
The packet created should contain 3 parts:
1. Original data (bit 0 to 7)
2. A tag to prevent resending a packet which has sent (bit 8)
3. A header so the receiver should check the correctness of data

### SND-3: Header should create using CRC (Functional)
Header of a packet should use cyclic redundancy check (CRC) method. Note that the tag should concatenate with the input data.

### SND-5: Received ACK should check its correctness (Functional)
There should be an uint8 acknowledgement (ACK). The ACK declares whether the data is sent successfully or not. The Ack should check and if it contains the desired value, we can get ready to send the next data. Note that if the ACK was correct, we should update the next ack value and the tag.

### SND-6: Timeout mechamism should be considered (Functional)
If no ACK received after 4 seconds, timeout should enable and resend the previous data again.

### SND-7: Reseting sender should be considered (Functional)
After sending a stream of data, the sender part should reset to its defaults.

### SND-8: ACK incrementation should check (Functional)
After ACK successfully received, it should increment for next check. This data is an uint8 value, so if it reach 15, it should set to 0 for the next value.

### SND-4: A state should be to wait for ACK (Functional)
After sending the packet, there should be a state so we wait until an acknowledgment (ACK) receive. If no ACK received after a time, we can resend the packet.

## Receiver: Clarifying requirements of receiver part (Functional)

### RCV-1: Packet should check its correctness (Functional)
There should be an uint16 input for packet received. Also, there should be an event for that packet indicating the presence of new packet. Then, it should check its correctness by checking the header. If the packet was not corrupted, the model should update its checking parameters like sending ACK value and tag. Also, the model should send an acknowledgement (ACK) to sender indicating that the packet has arrived successfully.

### RCV-2: A header should append to ACK (Functional)
To check the correctness of the ACK generated after receiving tha packet, there should append a header to the data of the ACK.

### RCV-3: ACK header should use CRC (Functional)
Header of a ACK should use cyclic redundancy check (CRC) method.

### RCV-4: Reseting receiver should be considered (Functional)
After receiving a stream of packets, the receiver part should reset to its defaults.
